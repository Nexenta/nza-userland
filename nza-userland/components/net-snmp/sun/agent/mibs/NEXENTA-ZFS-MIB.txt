-- Copyright 2013, Nexenta Systems, Inc.  All rights reserved.

NEXENTA-ZFS-MIB DEFINITIONS ::= BEGIN

IMPORTS
	zfs
		FROM NEXENTA-MIB
	MODULE-IDENTITY, OBJECT-TYPE, Unsigned32, Counter64, TimeTicks
		FROM SNMPv2-SMI
	TEXTUAL-CONVENTION, DisplayString, TruthValue
		FROM SNMPv2-TC;

nexentaZFSMIB MODULE-IDENTITY
	LAST-UPDATED "201304080000Z"
	ORGANIZATION "Nexenta Systems, Inc."
	CONTACT-INFO "Customer Support"
	DESCRIPTION "MIB exposing disk topology"
	REVISION    "201304080000Z"
	DESCRIPTION "Initial revision"

	::= { zfs 1 }

nexentaZFSMIBObjects OBJECT IDENTIFIER ::= { nexentaZFSMIB 1 }

NexentaZFSZpoolHealth ::= TEXTUAL-CONVENTION
		STATUS	     current
		DESCRIPTION
			"Represents ZFS zpool health"
		SYNTAX	     INTEGER {
			     degraded(1),
			     faulted(2),
			     offline(3),
			     online(4),
			     removed(5),
			     unavail(6),
			     online(7)
		}

NexentaZFSZpoolFailmode ::= TEXTUAL-CONVENTION
		STATUS	     current
		DESCRIPTION
			"Represents ZFS zpool failure mode"
		SYNTAX	     INTEGER {
			     wait(1),
			     continue(2),
			     panic(3)
		}

NexentaZFSRatio ::= TEXTUAL-CONVENTION
		DISPLAY-HINT "d-2"
		STATUS	     current
		DESCRIPTION
			"Represents ZFS ratio"
		SYNTAX	     INTEGER

nexentaZFSMIBARCObjects OBJECT IDENTIFIER ::= { nexentaZFSMIBObjects 1 }

	nexentaZFSARCTable OBJECT-TYPE
		SYNTAX	     SEQUENCE OF ARCEntry
		MAX-ACCESS   not-accessible
		STATUS	     current
		DESCRIPTION
			"ZFS conceptual table for ARC statistics"
		::= { nexentaZFSMIBARCObjects 1 }

	arcEntry OBJECT-TYPE
		SYNTAX		ARCEntry
		MAX-ACCESS	not-accessible
		STATUS		current
		DESCRIPTION
			"ARC statistics conceptual row"
		INDEX		{ arcInstance }
		::= { nexentaZFSARCTable 1 }

	ARCEntry ::= SEQUENCE {
		arcInstance			Unsigned32,
		arcMetaUsed			Unsigned32,
		arcC				Unsigned32,
		arcP				Unsigned32,
		arcSize				Unsigned32,
		arcL2SizeLow			Unsigned32,
		arcL2SizeHigh			Unsigned32,
		arcHits				Counter64,
		arcMisses			Counter64,
		arcDemandDataHits		Counter64,
		arcDemandDataMisses		Counter64,
		arcDemandMetadataHits		Counter64,
		arcDemandMetadataMisses		Counter64,
		arcPrefetchDataHits		Counter64,
		arcPrefetchDataMisses		Counter64,
		arcPrefetchMetadataHits		Counter64,
		arcPrefetchMetadataMisses	Counter64,
		arcMfuGhostHits			Counter64,
		arcMfuHits			Counter64,
		arcMruGhostHits			Counter64,
		arcMruHits			Counter64,
		arcL2Hits			Counter64,
		arcL2Misses			Counter64,
		arcCrTime			TimeTicks,
		arcSnapTime			TimeTicks
	}

	arcInstance OBJECT-TYPE
		SYNTAX		Unsigned32
		MAX-ACCESS	read-only
		STATUS		current
		DESCRIPTION
			"ARC instance identifier"
		::= { arcEntry 1 }

	arcMetaUsed OBJECT-TYPE
		SYNTAX		Unsigned32
		MAX-ACCESS	read-only
		STATUS		current
		DESCRIPTION
			"Current ARC metadata content in kilobytes"
		::= { arcEntry 2 }

	arcC OBJECT-TYPE
		SYNTAX		Unsigned32
		MAX-ACCESS	read-only
		STATUS		current
		DESCRIPTION
			"Current ARC target size in kilobytes"
		::= { arcEntry 3 }

	arcP OBJECT-TYPE
		SYNTAX		Unsigned32
		MAX-ACCESS	read-only
		STATUS		current
		DESCRIPTION
			"ARC MRU cache size in kilobytes"
		::= { arcEntry 4 }

	arcSize OBJECT-TYPE
		SYNTAX		Unsigned32
		MAX-ACCESS	read-only
		STATUS		current
		DESCRIPTION
			"ARC current size in kilobytes"
		::= { arcEntry 5 }

	arcL2SizeLow OBJECT-TYPE
		SYNTAX		Unsigned32
		MAX-ACCESS	read-only
		STATUS		current
		DESCRIPTION
			"L2ARC current size in kilobytes, lower-order, composed with arcL2SizeHigh"
		::= { arcEntry 6 }

	arcL2SizeHigh OBJECT-TYPE
		SYNTAX		Unsigned32
		MAX-ACCESS	read-only
		STATUS		current
		DESCRIPTION
			"L2ARC current size in kilobytes, higher-order, composed with arcL2SizeLow"
		::= { arcEntry 7 }

	arcHits OBJECT-TYPE
		 SYNTAX		Counter64
		 MAX-ACCESS	read-only
		 STATUS		current
		 DESCRIPTION
			"Number of ARC hits"
		::= { arcEntry 8 }

	arcMisses OBJECT-TYPE
		 SYNTAX		Counter64
		 MAX-ACCESS	read-only
		 STATUS		current
		 DESCRIPTION
			"Number of ARC misses"
		::= { arcEntry 9 }

	arcDemandDataHits OBJECT-TYPE
		 SYNTAX		Counter64
		 MAX-ACCESS	read-only
		 STATUS		current
		 DESCRIPTION
			"Number of on-demand ARC data cache hits"
		::= { arcEntry 10 }

	arcDemandDataMisses OBJECT-TYPE
		 SYNTAX		Counter64
		 MAX-ACCESS	read-only
		 STATUS		current
		 DESCRIPTION
			"Number of on-demand ARC data cache misses"
		::= { arcEntry 11 }

	arcDemandMetadataHits OBJECT-TYPE
		 SYNTAX		Counter64
		 MAX-ACCESS	read-only
		 STATUS		current
		 DESCRIPTION
			"Number of demand-driven ARC metadata cache hits"
		::= { arcEntry 12 }

	arcDemandMetadataMisses OBJECT-TYPE
		 SYNTAX		Counter64
		 MAX-ACCESS	read-only
		 STATUS		current
		 DESCRIPTION
			"Number of demand-driven ARC metadata cache misses"
		::= { arcEntry 13 }

	arcPrefetchDataHits OBJECT-TYPE
		 SYNTAX		Counter64
		 MAX-ACCESS	read-only
		 STATUS		current
		 DESCRIPTION
			"Number of prefetched ARC data cache hits"
		::= { arcEntry 14 }

	arcPrefetchDataMisses OBJECT-TYPE
		 SYNTAX		Counter64
		 MAX-ACCESS	read-only
		 STATUS		current
		 DESCRIPTION
			"Number of prefetched ARC data cache misses"
		::= { arcEntry 15 }

	arcPrefetchMetadataHits OBJECT-TYPE
		 SYNTAX		Counter64
		 MAX-ACCESS	read-only
		 STATUS		current
		 DESCRIPTION
			"Number of prefetched ARC metadata cache hits"
		::= { arcEntry 16 }

	arcPrefetchMetadataMisses OBJECT-TYPE
		 SYNTAX		Counter64
		 MAX-ACCESS	read-only
		 STATUS		current
		 DESCRIPTION
			"Number of prefetched ARC metadata cache misses"
		::= { arcEntry 17 }

	arcMfuGhostHits OBJECT-TYPE
		 SYNTAX		Counter64
		 MAX-ACCESS	read-only
		 STATUS		current
		 DESCRIPTION
			"Number of MFU cache ghost hits"
		::= { arcEntry 18 }

	arcMfuHits OBJECT-TYPE
		 SYNTAX		Counter64
		 MAX-ACCESS	read-only
		 STATUS		current
		 DESCRIPTION
			"Number of MFU cache hits"
		::= { arcEntry 19 }

	arcMruGhostHits OBJECT-TYPE
		 SYNTAX		Counter64
		 MAX-ACCESS	read-only
		 STATUS		current
		 DESCRIPTION
			"Number of MRU cache ghost hits"
		::= { arcEntry 20 }

	arcMruHits OBJECT-TYPE
		 SYNTAX		Counter64
		 MAX-ACCESS	read-only
		 STATUS		current
		 DESCRIPTION
			"Number of MRU cache hits"
		::= { arcEntry 21 }

	arcL2Hits OBJECT-TYPE
		 SYNTAX		Counter64
		 MAX-ACCESS	read-only
		 STATUS		current
		 DESCRIPTION
			"Number of L2ARC cache hits"
		::= { arcEntry 22 }

	arcL2Misses OBJECT-TYPE
		 SYNTAX		Counter64
		 MAX-ACCESS	read-only
		 STATUS		current
		 DESCRIPTION
			"Number of L2ARC cache misses"
		::= { arcEntry 23 }

	arcCrTime OBJECT-TYPE
		 SYNTAX		TimeTicks
		 MAX-ACCESS	read-only
		 STATUS		current
		 DESCRIPTION
			"ARC statistics creation time in hundredths of a second since boot"
		::= { arcEntry 24 }

	arcSnapTime OBJECT-TYPE
		 SYNTAX		TimeTicks
		 MAX-ACCESS	read-only
		 STATUS		current
		 DESCRIPTION
			"ARC statistics update time in hundredths of a second since boot"
		::= { arcEntry 25 }

nexentaZFSMIBZpoolObjects OBJECT IDENTIFIER ::= { nexentaZFSMIBObjects 2 }

	nexentaZFSZpoolTable OBJECT-TYPE
		SYNTAX	     SEQUENCE OF ZpoolEntry
		MAX-ACCESS   not-accessible
		STATUS	     current
		DESCRIPTION
			"ZFS conceptual table for zpool statistics"
		::= { nexentaZFSMIBZpoolObjects 1 }

	zpoolEntry OBJECT-TYPE
		SYNTAX		ZpoolEntry
		MAX-ACCESS	not-accessible
		STATUS		current
		DESCRIPTION
			"ZFS zpool statistics conceptual row"
		INDEX		{ zpoolName, zpoolGuid }
		::= { nexentaZFSZpoolTable 1 }

	ZpoolEntry ::= SEQUENCE {
		zpoolName			DisplayString,
		zpoolGuid			DisplayString,
		zpoolHealth			NexentaZFSZpoolHealth,
		zpoolFailmode			NexentaZFSZpoolFailmode,
		zpoolCapacity			Unsigned32,
		zpoolSizeHigh			Unsigned32,
		zpoolSizeLow			Unsigned32,
		zpoolAllocHigh			Unsigned32,
		zpoolAllocLow			Unsigned32,
		zpoolFreeHigh			Unsigned32,
		zpoolFreeLow			Unsigned32,
		zpoolFreeingHigh		Unsigned32,
		zpoolFreeingLow			Unsigned32,
		zpoolExpandSizeHigh		Unsigned32,
		zpoolExpandSizeLow		Unsigned32,
		zpoolDedupRatio			NexentaZFSRatio,
		zpoolAutoexpand			TruthValue
	}

	zpoolName OBJECT-TYPE
		SYNTAX		DisplayString
		MAX-ACCESS	read-only
		STATUS		current
		DESCRIPTION
			"zpool Name"
		::= { zpoolEntry 1 }

	zpoolGuid OBJECT-TYPE
		SYNTAX		DisplayString
		MAX-ACCESS	read-only
		STATUS		current
		DESCRIPTION
			"zpool GUID"
		::= { zpoolEntry 2 }

	zpoolHealth OBJECT-TYPE
		SYNTAX		NexentaZFSZpoolHealth
		MAX-ACCESS	read-only
		STATUS		current
		DESCRIPTION
			"zpool health state"
		::= { zpoolEntry 3 }

	zpoolFailmode OBJECT-TYPE
		SYNTAX		NexentaZFSZpoolFailmode
		MAX-ACCESS	read-only
		STATUS		current
		DESCRIPTION
			"zpool failure mode"
		::= { zpoolEntry 4 }

	zpoolCapacity OBJECT-TYPE
		SYNTAX		Unsigned32 (0..100)
		MAX-ACCESS	read-only
		STATUS		current
		DESCRIPTION
			"zpool capacity as decimal percentage"
		::= { zpoolEntry 5 }

	zpoolSizeHigh OBJECT-TYPE
		SYNTAX		Unsigned32
		MAX-ACCESS	read-only
		STATUS		current
		DESCRIPTION
			"zpool total size in kilobytes, high-order byte, must be composed with zpoolSizeLow"
		::= { zpoolEntry 6 }

	zpoolSizeLow OBJECT-TYPE
		SYNTAX		Unsigned32
		MAX-ACCESS	read-only
		STATUS		current
		DESCRIPTION
			"zpool total size in kilobytes, low-order byte, must be composed with zpoolSizeHigh"
		::= { zpoolEntry 7 }

	zpoolAllocHigh OBJECT-TYPE
		SYNTAX		Unsigned32
		MAX-ACCESS	read-only
		STATUS		current
		DESCRIPTION
			"zpool allocated space in kilobytes, high-order byte, must be composed with zpoolAllocLow"
		::= { zpoolEntry 8 }

	zpoolAllocLow OBJECT-TYPE
		SYNTAX		Unsigned32
		MAX-ACCESS	read-only
		STATUS		current
		DESCRIPTION
			"zpool allocated space in kilobytes, low-order byte, must be composed with zpoolAllocHigh"
		::= { zpoolEntry 9 }

	zpoolFreeHigh OBJECT-TYPE
		SYNTAX		Unsigned32
		MAX-ACCESS	read-only
		STATUS		current
		DESCRIPTION
			"zpool free space in kilobytes, high-order byte, must be composed with zpoolFreeLow"
		::= { zpoolEntry 10 }

	zpoolFreeLow OBJECT-TYPE
		SYNTAX		Unsigned32
		MAX-ACCESS	read-only
		STATUS		current
		DESCRIPTION
			"zpool allocated space in kilobytes, low-order byte, must be composed with zpoolFreeHigh"
		::= { zpoolEntry 11 }

	zpoolFreeingHigh OBJECT-TYPE
		SYNTAX		Unsigned32
		MAX-ACCESS	read-only
		STATUS		current
		DESCRIPTION
			"zpool space pending async free in kilobytes, high-order byte, must be composed with zpoolFreeingLow"
		::= { zpoolEntry 12 }

	zpoolFreeingLow OBJECT-TYPE
		SYNTAX		Unsigned32
		MAX-ACCESS	read-only
		STATUS		current
		DESCRIPTION
			"zpool space pending async free in kilobytes, low-order byte, must be composed with zpoolFreeingHigh"
		::= { zpoolEntry 13 }

	zpoolExpandSizeHigh OBJECT-TYPE
		SYNTAX		Unsigned32
		MAX-ACCESS	read-only
		STATUS		current
		DESCRIPTION
			"zpool available expansion space in kilobytes, high-order byte, must be composed with zpoolExpandSizeLow"
		::= { zpoolEntry 14 }

	zpoolExpandSizeLow OBJECT-TYPE
		SYNTAX		Unsigned32
		MAX-ACCESS	read-only
		STATUS		current
		DESCRIPTION
			"zpool available expansion space in kilobytes, high-order byte, must be composed with zpoolExpandSizeHigh"
		::= { zpoolEntry 15 }

	zpoolDedupRatio OBJECT-TYPE
		SYNTAX		NexentaZFSRatio
		MAX-ACCESS	read-only
		STATUS		current
		DESCRIPTION
			"zpool deduplication ratio, precise to two decimals"
		::= { zpoolEntry 16 }

	zpoolAutoexpand OBJECT-TYPE
		SYNTAX		TruthValue
		MAX-ACCESS	read-only
		STATUS		current
		DESCRIPTION
			"zpool automatically expands to use new space"
		::= { zpoolEntry 17 }

END
